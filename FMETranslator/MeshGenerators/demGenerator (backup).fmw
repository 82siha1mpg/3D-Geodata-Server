FME workspace demGenerator (backup).fmw

Parameters:
- DestDataset_GEOTIFF = $(FME_MF_DIR)Data-OpenNRW\Assets\terrain\testdelete   # Destination GeoTIFF Folder
- SourceDataset_POINTCLOUDXYZ = $(FME_MF_DIR)Data-OpenNRW\DEM\dgm1l_05314000_Bonn_EPSG25832_XYZ\dgm1l-ab_32360_5613_1_nw.xyz   # Point Cloud XYZ File(s)

Readers:
- POINTCLOUDXYZ_1: POINTCLOUDXYZ from $(SourceDataset_POINTCLOUDXYZ) in EPSG:25832

Writers:
- GEOTIFF_1: GEOTIFF to $(DestDataset_GEOTIFF) in EPSG:4326

POINTCLOUDXYZ (reader POINTCLOUDXYZ_1)
    -> RasterDemGenerator [POINTS/LINES]
RasterDemGenerator: RasterDEMGenerator
    INTERPOLATION_TYPE = AUTO
    NODATA_VALUE = 0
    TOLERANCE = 0.3
    X_SPACING = 10
    Y_SPACING = 10
    DEM_RASTER -> BonnDem_32372_5620_2_10x10 (writer GEOTIFF_1)
BonnDem_32372_5620_2_10x10 (writer GEOTIFF_1)
