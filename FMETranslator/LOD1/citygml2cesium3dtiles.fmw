FME workspace citygml2cesium3dtiles.fmw

Parameters:
- DestDataset_CESIUM3DTILES = D:\HFT Course Material\Sem 3\SERVERS\tools-tiles-editor\GML Update test\2object   # Destination Cesium 3D Tiles Folder
- SourceDataset_CITYGML = D:\HFT Course Material\Sem 3\SERVERS\tools-tiles-editor\GML Update test\two_objects.gml   # Source CityGML File(s)

Readers:
- CITYGML_1: CITYGML from $(SourceDataset_CITYGML) in EPSG:25832

Writers:
- CESIUM3DTILES_1: CESIUM3DTILES to $(DestDataset_CESIUM3DTILES) in EPSG:25832

Address (reader CITYGML_1)
    attributes: citygml_target_uri xml_buffer, citygml_feature_role xml_buffer, citygml_feature_role_attr_name xml_buffer, citygml_feature_role_attr_val xml_buffer, gml_description xml_buffer, gml_name xml_buffer, citygml_address xml_xml
    -> tileset (writer CESIUM3DTILES_1)
Building (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_function xml_buffer, citygml_measured_height xml_real64, citygml_measured_height_units xml_buffer, citygml_storeys_above_ground xml_uint64, citygml_storeys_below_ground xml_uint64, citygml_level_of_detail{} xml_buffer, citygml_consists_of_building_part{}.xlink_href xml_buffer, citygml_address{}.xlink_href xml_buffer, BezugspunktDach xml_buffer, DatenquelleBodenhoehe xml_buffer, DatenquelleDachhoehe xml_buffer, DatenquelleLage xml_buffer, Gemeindeschluessel xml_buffer
    -> tileset (writer CESIUM3DTILES_1)
BuildingPart (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_function xml_buffer, citygml_measured_height xml_real64, citygml_measured_height_units xml_buffer, citygml_storeys_above_ground xml_uint64, citygml_storeys_below_ground xml_uint64, citygml_level_of_detail{} xml_buffer, citygml_consists_of_building_part{}.xlink_href xml_buffer, citygml_address{}.xlink_href xml_buffer, BezugspunktDach xml_buffer, DatenquelleBodenhoehe xml_buffer, DatenquelleDachhoehe xml_buffer, DatenquelleLage xml_buffer
    -> tileset (writer CESIUM3DTILES_1)
CityModel (reader CITYGML_1)
    attributes: citygml_target_uri xml_buffer, gml_description xml_buffer, gml_name xml_buffer, citygml_city_object_member{}.xlink_href xml_buffer, gml_feature_member{}.xlink_href xml_buffer
    -> tileset (writer CESIUM3DTILES_1)
tileset (writer CESIUM3DTILES_1)
    attributes: gml_id string, gml_parent_id string, citygml_target_uri string, citygml_feature_role string, citygml_feature_role_attr_name string, citygml_feature_role_attr_val string, gml_description string, gml_name string, citygml_address string, citygml_creationDate string, citygml_terminationDate string, externalReference{}.externalObject.name string, externalReference{}.externalObject.uri string, externalReference{}.informationSystem string, citygml_function string, citygml_measured_height float, citygml_measured_height_units string, citygml_storeys_above_ground string, citygml_storeys_below_ground string, citygml_level_of_detail{} string, citygml_consists_of_building_part{}.xlink_href string, citygml_address{}.xlink_href string, BezugspunktDach string, DatenquelleBodenhoehe string, DatenquelleDachhoehe string, DatenquelleLage string, Gemeindeschluessel string, citygml_city_object_member{}.xlink_href string, gml_feature_member{}.xlink_href string
