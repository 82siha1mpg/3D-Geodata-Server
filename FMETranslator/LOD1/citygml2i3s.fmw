FME workspace citygml2i3s.fmw

Parameters:
- SourceDataset_CITYGML = D:\HFT Course Material\Sem 3\Data- Open NRW\LOD1\3d-gm_lod1_05954000_Ennepe-Ruhr-Kreis_EPSG25832_CityGML.zip   # Source CityGML File(s)
- DestDataset_I3S = D:\HFT Course Material\Sem 3\SERVERS\GeoServer\Assets\LOD1\I3s\Ennepe-Ruhr-KreisFull   # Destination Indexed 3D Layer Folder

Readers:
- CITYGML_1: CITYGML from $(SourceDataset_CITYGML) in EPSG:25832

Writers:
- I3S_1: I3S to $(DestDataset_I3S) in EPSG:4326

Note: Workspace description / Illustrates how to translate CityGML to Indexed 3D Scene. / Workflow description / Add source data i.e. CityGML (Readers -> Add CityGML Reader). / Set Coordinate Reference of input data. / Set GML Axis Order. / Add 'ESRI I3S' Writer. / Pre-requisites / none

Bookmark: Source Data
CityModel (reader CITYGML_1)
    attributes: citygml_target_uri xml_buffer, gml_description xml_buffer, gml_name xml_buffer, citygml_city_object_member{}.xlink_href xml_buffer, gml_feature_member{}.xlink_href xml_buffer
    -> layer (writer I3S_1)
BuildingPart (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_function xml_buffer, citygml_measured_height xml_real64, citygml_measured_height_units xml_buffer, citygml_storeys_above_ground xml_uint64, citygml_storeys_below_ground xml_uint64, citygml_level_of_detail{} xml_buffer, citygml_consists_of_building_part{}.xlink_href xml_buffer, citygml_address{}.xlink_href xml_buffer, BezugspunktDach xml_buffer, DatenquelleBodenhoehe xml_buffer, DatenquelleDachhoehe xml_buffer, DatenquelleLage xml_buffer
    -> layer (writer I3S_1)
Building (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_function xml_buffer, citygml_measured_height xml_real64, citygml_measured_height_units xml_buffer, citygml_storeys_above_ground xml_uint64, citygml_storeys_below_ground xml_uint64, citygml_level_of_detail{} xml_buffer, citygml_consists_of_building_part{}.xlink_href xml_buffer, citygml_address{}.xlink_href xml_buffer, BezugspunktDach xml_buffer, DatenquelleBodenhoehe xml_buffer, DatenquelleDachhoehe xml_buffer, DatenquelleLage xml_buffer, Gemeindeschluessel xml_buffer
    -> layer (writer I3S_1)
Address (reader CITYGML_1)
    attributes: citygml_target_uri xml_buffer, citygml_feature_role xml_buffer, citygml_feature_role_attr_name xml_buffer, citygml_feature_role_attr_val xml_buffer, gml_description xml_buffer, gml_name xml_buffer, citygml_address xml_xml
    -> layer (writer I3S_1)

Bookmark: Output: Index 3D Scene
layer (writer I3S_1)
    attributes: gml_id string, citygml_target_uri string, gml_description string, gml_name string, citygml_city_object_member{}.xlink_href string, gml_feature_member{}.xlink_href string, gml_parent_id string, citygml_feature_role string, citygml_feature_role_attr_name string, citygml_feature_role_attr_val string, citygml_creationDate string, citygml_terminationDate string, externalReference{}.externalObject.name string, externalReference{}.externalObject.uri string, externalReference{}.informationSystem string, citygml_function string, citygml_measured_height float64, citygml_measured_height_units string, citygml_storeys_above_ground string, citygml_storeys_below_ground string, citygml_level_of_detail{} string, citygml_consists_of_building_part{}.xlink_href string, citygml_address{}.xlink_href string, BezugspunktDach string, DatenquelleBodenhoehe string, DatenquelleDachhoehe string, DatenquelleLage string, citygml_address string, Gemeindeschluessel string
